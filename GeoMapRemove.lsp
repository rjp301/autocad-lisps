(defun c:geomapremove (/ Ctab Layout)
	(princ "\nCapture Geomap of all viewports")
 	(setq Ctab (getvar "CTAB"))
 	(foreach Layout (reverse (layoutlist))
   		(command "LAYOUT" "S" Layout)
   		(command "MSPACE")
		(command "_GEOMAP" "OFF")
		(command "PSPACE")
 	)
	(setvar "CTAB" Ctab)
	(princ)
)
