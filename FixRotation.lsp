(defun c:fixrotation (/ Ctab Layout)
	(princ "\n Zoom extents all layouts")
 	(setq Ctab (getvar "CTAB"))
 	(foreach Layout (layoutlist)
   		(command "LAYOUT" "S" Layout)
   		(command "MOVE" "ALL" "" "267.4,0" "0,0")
		(command "ROTATE" "ALL" "" "6,6" "90")
 	)
	(setvar "CTAB" Ctab)
	(princ)
)
