(defun c:allannoallvisible (/ Ctab Layout)
	(princ "\nMake annotative objects visible on all layouts")
 	(setq Ctab (getvar "CTAB"))
 	(foreach Layout (reverse (layoutlist))
   		(command "LAYOUT" "S" Layout)
		(command "ANNOALLVISIBLE" "1")
 	)
	(setvar "CTAB" Ctab)
	(princ)
)
