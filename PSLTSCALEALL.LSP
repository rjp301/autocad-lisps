(defun c:PSLTSCALEALL (/ Ctab Layout)
	(princ "\nCapture Geomap of all viewports")
 	(setq Ctab (getvar "CTAB"))
 	(foreach Layout (reverse (layoutlist))
   		(command "LAYOUT" "S" Layout)
   		(command "PSLTSCALE" "0")
 	)
	(setvar "CTAB" Ctab)
	(command "REGENALL")
	(princ)
)
