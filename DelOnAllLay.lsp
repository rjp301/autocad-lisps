(defun c:usewithcaution	(/ p1 p2 ss)
 (vl-load-com)
 (if (and (= 0 (getvar 'tilemode))
   (setq p1 (getpoint "\nSpecify first corner point: "))
   (setq p2 (getcorner p1 "\nSpecify other corner point: "))
 )
 (foreach tab (layoutlist)
   (setvar 'ctab tab)
   (and (= 1 (getvar 'cvport)) (vlax-invoke (vlax-get-acad-object) 'zoomwindow p1 p2))
   (if (setq ss (ssget "W" p1 p2 (list (cons 410 tab))))
     (mapcar 'entdel (vl-remove-if 'listp (mapcar 'cadr (ssnamex ss))))
   )
 )
 )
 (princ)
)
