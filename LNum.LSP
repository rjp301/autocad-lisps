(defun c:LNum (/ Ctab Layout)
	(princ "\n Incrementally numbers all layouts")
 	(setq Ctab (getvar "CTAB"))
	(setq num 1)
 	(foreach Layout (layoutlist)
   		(command "LAYOUT" "S" Layout)
   		(command "LAYOUT" "R" Layout (itoa num))
		(setq num (1+ num))
 	)
	(setvar "CTAB" Ctab)
	(princ)
)
