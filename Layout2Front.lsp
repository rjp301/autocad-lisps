(defun c:layout2front (/ Ctab Layout)
	(princ "\nCapture Geomap of all viewports")
 	(setq Ctab (getvar "CTAB"))
 	(foreach Layout (reverse (layoutlist))
   		(command "LAYOUT" "S" Layout)
   		(setq ss (ssget "x" (list (cons 8 "LAYOUT")(cons 8 "LAYOUT - Column Divider"))))
		(command "draworder" ss "" "Front")
 	)
	(setvar "CTAB" Ctab)
	(princ)
)
